FME workspace 1_4.fmw

Parameters:
- SourceDataset_CSV2 = $(FME_MF_DIR)routePoints.csv   # Source CSV (Comma Separated Value) File(s)
- SourceDataset_SHAPEFILE = ""C:\Users\User\Desktop\Geoinformatyka\5 semestr\Bazy\lab3\Dane\T2019_KAR_POI_TABLE.shp" "C:\Users\User\Desktop\Geoinformatyka\5 semestr\Bazy\lab3\Dane\T2019_KAR_STREET_NODE.shp" "C:\Users\User\Desktop\Geoinformatyka\5 semestr\Bazy\lab3\Dane\T2019_KAR_STREETS.shp""   # Source Esri Shapefile(s)

Readers:
- CSV2_1: CSV2 from $(SourceDataset_CSV2)
- SHAPEFILE_1: SHAPEFILE from $(SourceDataset_SHAPEFILE) in WGS84

T2019_KAR_POI_TABLE (reader SHAPEFILE_1)
    attributes: POI_ID long, LINK_ID long, TYPE varchar(250), POI_NAME varchar(250), ST_NAME varchar(250), LAT number(31,15), LON number(31,15)
    -> T2019_KAR_POI_TABLE
    -> Reprojector
T2019_KAR_POI_TABLE: Inspector
T2019_KAR_STREET_NODE (reader SHAPEFILE_1)
    attributes: NODE_ID long, LINK_ID long, POINT_NUM long, Z_LEVEL long, INTERSECT varchar(1), LAT number(31,15), LON number(31,15)
    -> T2019_KAR_STREET_NODE
    -> Reprojector
T2019_KAR_STREET_NODE: Inspector
T2019_KAR_STREETS (reader SHAPEFILE_1)
    attributes: LINK_ID long, ST_NAME varchar(254), REF_IN_ID long, NREF_IN_ID long, FUNC_CLASS varchar(1), SPEED_CAT varchar(1), FR_SPEED_L long, TO_SPEED_L long, DIR_TRAVEL varchar(1)
    -> T2019_KAR_STREETS
    -> Reprojector
T2019_KAR_STREETS: Inspector
CSV (reader CSV2_1)
    attributes: x x_coordinate, y y_coordinate
    -> VertexCreator
VertexCreator
    MEASURE_TYPE = Continuous
    MODE_NAME = Replace with Point
    XVAL = @Value(x)
    YVAL = @Value(y)
    -> LineBuilder
LineBuilder
    ACCUM_INPUT_ATTRS = Use Attributes From One Feature
    REMOVE_DUPLICATES = NO
    LINE -> Reprojector
Reprojector
    DEST = DHDN.Berlin/Cassini
    INTERPOLATION_TYPE_NAME = Nearest Neighbor
    RASTER_CELL_SIZE = Preserve Cells
    RASTER_TOLERANCE = 0.0
