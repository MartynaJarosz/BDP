FME workspace 5_7.fmw

Parameters:
- SourceDataset_SHAPEFILE_5 = C:\Users\User\Desktop\Geoinformatyka\5 semestr\Bazy\lab3\Dane\T2019_KAR_STREETS.shp   # Source Esri Shapefile(s)
- SourceDataset_CSV2 = $(FME_MF_DIR)routePoints.csv   # Source CSV (Comma Separated Value) File(s)
- SourceDataset_SHAPEFILE = C:\Users\User\Desktop\Geoinformatyka\5 semestr\Bazy\lab3\Dane\T2019_KAR_STREETS.shp   # Source Esri Shapefile(s)
- SourceDataset_CSV2_3 = $(FME_MF_DIR)routePoints.csv   # Source CSV (Comma Separated Value) File(s)
- SourceDataset_SHAPEFILE_7 = C:\Users\User\Desktop\Geoinformatyka\5 semestr\Bazy\lab3\Dane\T2019_KAR_POI_TABLE.shp   # Source Esri Shapefile(s)
- DestDataset_GEOJSON_5 = $(FME_MF_DIR)POI_5m_1.json   # Destination GeoJSON File
- DestDataset_GEOJSON_4 = $(FME_MF_DIR)POI_5m_2.json   # Destination GeoJSON File
- DestDataset_GEODATABASE_FILE_3 = $(FME_MF_DIR)Esri_Geodatabase2.gdb   # File Geodatabase
- DestDataset_GEODATABASE_FILE = $(FME_MF_DIR)Esri_Geodatabase1.gdb   # File Geodatabase
- SourceDataset_SHAPEFILE_6 = C:\Users\User\Desktop\Geoinformatyka\5 semestr\Bazy\lab3\Dane\T2019_KAR_STREET_NODE.shp   # Source Esri Shapefile(s)

Readers:
- SHAPEFILE_2: SHAPEFILE from $(SourceDataset_SHAPEFILE_5) in WGS84
- CSV2_1: CSV2 from $(SourceDataset_CSV2)
- SHAPEFILE_1: SHAPEFILE from $(SourceDataset_SHAPEFILE) in WGS84
- CSV2_2: CSV2 from $(SourceDataset_CSV2_3)
- SHAPEFILE_3: SHAPEFILE from $(SourceDataset_SHAPEFILE_7) in WGS84
- SHAPEFILE_4: SHAPEFILE from $(SourceDataset_SHAPEFILE_6) in WGS84

Writers:
- GEOJSON_2: GEOJSON to $(DestDataset_GEOJSON_5)
- GEOJSON_3: GEOJSON to $(DestDataset_GEOJSON_4)
- GEODATABASE_FILE_1: GEODATABASE_FILE to $(DestDataset_GEODATABASE_FILE) in DHDN.Berlin/Cassini
- GEODATABASE_FILE_2: GEODATABASE_FILE to $(DestDataset_GEODATABASE_FILE_3) in DHDN.Berlin/Cassini

CSV (reader CSV2_2)
    attributes: x x_coordinate, y y_coordinate
    -> VertexCreator_2
VertexCreator_2
    MEASURE_TYPE = Continuous
    MODE_NAME = Replace with Point
    XVAL = @Value(x)
    YVAL = @Value(y)
    -> LineBuilder_2
LineBuilder_2
    ACCUM_INPUT_ATTRS = Use Attributes From One Feature
    REMOVE_DUPLICATES = NO
    LINE -> Reprojector_4
Reprojector_4
    DEST = DHDN.Berlin/Cassini
    INTERPOLATION_TYPE_NAME = Nearest Neighbor
    RASTER_CELL_SIZE = Preserve Cells
    RASTER_TOLERANCE = 0.0
    REPROJECTED -> ShortestPathFinder_2 [FROM-TO]
T2019_KAR_STREETS (reader SHAPEFILE_2)
    attributes: LINK_ID long, ST_NAME varchar(254), REF_IN_ID long, NREF_IN_ID long, FUNC_CLASS varchar(1), SPEED_CAT varchar(1), FR_SPEED_L long, TO_SPEED_L long, DIR_TRAVEL varchar(1)
    -> Reprojector
Reprojector
    DEST = DHDN.Berlin/Cassini
    INTERPOLATION_TYPE_NAME = Nearest Neighbor
    RASTER_CELL_SIZE = Preserve Cells
    RASTER_TOLERANCE = 0.0
    REPROJECTED -> Tester_2
Tester_2
    BOOL_OP = OR
    TEST_CLAUSE = TEST @Value(DIR_TRAVEL) = F
    TEST_MODE = TEST
    PASSED -> AttributeManager_3
    FAILED -> AttributeManager_4
AttributeManager_3
    ATTR_TABLE:
      SET_TO ForwardCost = @Evaluate(1*@Length())
      SET_TO ReverseCost = @Evaluate(9999*@Length())
    -> ShortestPathFinder [NETWORK]
AttributeManager_4
    ATTR_TABLE:
      SET_TO ForwardCost = @Evaluate(1*@Length())
      SET_TO ReverseCost = @Evaluate(1*@Length())
    -> ShortestPathFinder [NETWORK]
CSV (reader CSV2_1)
    attributes: x x_coordinate, y y_coordinate
    -> VertexCreator
VertexCreator
    MEASURE_TYPE = Continuous
    MODE_NAME = Replace with Point
    XVAL = @Value(x)
    YVAL = @Value(y)
    -> LineBuilder
LineBuilder
    ACCUM_INPUT_ATTRS = Use Attributes From One Feature
    REMOVE_DUPLICATES = NO
    LINE -> Reprojector_2
Reprojector_2
    DEST = DHDN.Berlin/Cassini
    INTERPOLATION_TYPE_NAME = Nearest Neighbor
    RASTER_CELL_SIZE = Preserve Cells
    RASTER_TOLERANCE = 0.0
    REPROJECTED -> ShortestPathFinder [FROM-TO]
ShortestPathFinder
    ALLOW_UTURNS = Yes
    REORDER_MODE = NONE
    SNAP_POINTS = No
    WEIGHT_ATTR_1 = ForwardCost
    WEIGHT_ATTR_2 = ReverseCost
    WEIGHT_ATTR_CHOICE = BY_TWO_ATTRIBUTES
    PATH -> Bufferer
    PATH -> LengthCalculator
    PATH -> SpatialFilter_4 [Filter]
Bufferer
    ANGLE = 22.5
    CAP_STYLE = Arc
    CORNER_STYLE = Arc
    MODE = AREA
    OFFSET = 5
    OFFSET_UNITS = METERS
    PRECISION = APPROX
    BUFFERED -> SpatialFilter_2 [Filter]
LengthCalculator
    DIM = 2
    LEN_ATTR = _length
    MULT = 1
    -> Esri_Geodb2 (writer GEODATABASE_FILE_2)
T2019_KAR_STREETS (reader SHAPEFILE_1)
    attributes: LINK_ID long, ST_NAME varchar(254), REF_IN_ID long, NREF_IN_ID long, FUNC_CLASS varchar(1), SPEED_CAT varchar(1), FR_SPEED_L long, TO_SPEED_L long, DIR_TRAVEL varchar(1)
    -> Reprojector_3
Reprojector_3
    DEST = DHDN.Berlin/Cassini
    INTERPOLATION_TYPE_NAME = Nearest Neighbor
    RASTER_CELL_SIZE = Preserve Cells
    RASTER_TOLERANCE = 0.0
    REPROJECTED -> ShortestPathFinder_2 [NETWORK]
ShortestPathFinder_2
    ALLOW_UTURNS = Yes
    REORDER_MODE = NONE
    SNAP_POINTS = No
    WEIGHT_ATTR_CHOICE = BY_LENGTH
    PATH -> ShortestPathFinder_Path_2
    PATH -> Bufferer_2
    PATH -> LengthCalculator_2
    PATH -> SpatialFilter_3 [Filter]
ShortestPathFinder_Path_2: Inspector
Bufferer_2
    ANGLE = 22.5
    CAP_STYLE = Arc
    CORNER_STYLE = Arc
    MODE = AREA
    OFFSET = 5
    OFFSET_UNITS = METERS
    PRECISION = APPROX
    BUFFERED -> SpatialFilter [Filter]
    BUFFERED -> Bufferer_2_Buffered
Bufferer_2_Buffered: Inspector
LengthCalculator_2
    DIM = 2
    LEN_ATTR = _length
    MULT = 1
    -> Esri_Geodb1 (writer GEODATABASE_FILE_1)
T2019_KAR_POI_TABLE (reader SHAPEFILE_3)
    attributes: POI_ID long, LINK_ID long, TYPE varchar(250), POI_NAME varchar(250), ST_NAME varchar(250), LAT number(31,15), LON number(31,15)
    -> Reprojector_5
Reprojector_5
    DEST = DHDN.Berlin/Cassini
    INTERPOLATION_TYPE_NAME = Nearest Neighbor
    RASTER_CELL_SIZE = Preserve Cells
    RASTER_TOLERANCE = 0.0
    REPROJECTED -> SpatialFilter [Candidate]
    REPROJECTED -> SpatialFilter_2 [Candidate]
SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = CONTAINS
    USE_BOUNDING_BOX = No
    PASSED -> POI_5m_1 (writer GEOJSON_2)
POI_5m_1 (writer GEOJSON_2)
    attributes: POI_ID int, LINK_ID int, TYPE string, POI_NAME string, ST_NAME string, LAT float, LON float
SpatialFilter_2
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> POI_5m_2 (writer GEOJSON_3)
POI_5m_2 (writer GEOJSON_3)
    attributes: POI_ID int, LINK_ID int, TYPE string, POI_NAME string, ST_NAME string, LAT float, LON float
T2019_KAR_STREET_NODE (reader SHAPEFILE_4)
    attributes: NODE_ID long, LINK_ID long, POINT_NUM long, Z_LEVEL long, INTERSECT varchar(1), LAT number(31,15), LON number(31,15)
    -> Reprojector_6
Reprojector_6
    DEST = DHDN.Berlin/Cassini
    INTERPOLATION_TYPE_NAME = Nearest Neighbor
    RASTER_CELL_SIZE = Preserve Cells
    RASTER_TOLERANCE = 0.0
    REPROJECTED -> streets_node_reprojected
    REPROJECTED -> SpatialFilter_3 [Candidate]
    REPROJECTED -> SpatialFilter_4 [Candidate]
SpatialFilter_3
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> StatisticsCalculator
StatisticsCalculator
    CALCULATION_MODE = NUMERIC
    FEAT_STATS = POINT_NUM,NUMERIC_MODE,MIN,MAX,COUNT,SUM,MEAN,MEDIAN,,,,,,,
    SUMMARY -> Esri_Geodb1 (writer GEODATABASE_FILE_1)
Esri_Geodb1 (writer GEODATABASE_FILE_1)
    attributes: POINT_NUM_min integer, POINT_NUM_max integer, POINT_NUM_total_count char(20), POINT_NUM_sum double, POINT_NUM_mean double, POINT_NUM_median double, x double, y double, _total_cost char(2048), _length double
streets_node_reprojected: Inspector
SpatialFilter_4
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> StatisticsCalculator_2
StatisticsCalculator_2
    CALCULATION_MODE = NUMERIC
    FEAT_STATS = POINT_NUM,NUMERIC_MODE,MIN,MAX,COUNT,SUM,MEAN,MEDIAN,,,,,,,
    SUMMARY -> Esri_Geodb2 (writer GEODATABASE_FILE_2)
Esri_Geodb2 (writer GEODATABASE_FILE_2)
    attributes: x double, y double, _total_cost char(2048), _length double, POINT_NUM_min integer, POINT_NUM_max integer, POINT_NUM_total_count char(20), POINT_NUM_sum double, POINT_NUM_mean double, POINT_NUM_median double
